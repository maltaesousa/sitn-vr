FME workspace 10_LandCover_Extractor.fmw

Parameters:
- DestDataset_ESRISHAPE = .   # Destination Esri Shapefile Folder
- SourceDataset_ESRISHAPE = ..\00_perimeter\secteurs.shp   # Source Esri Shapefile(s)
- SourceDataset_POSTGIS = sitn_data   # Database

Readers:
- POSTGIS_1: POSTGIS from $(SourceDataset_POSTGIS) in EPSG:2056
- ESRISHAPE_1: ESRISHAPE from $(SourceDataset_ESRISHAPE)

Writers:
- ESRISHAPE_2: ESRISHAPE to $(DestDataset_ESRISHAPE)

Note: Land cover extraction. / Adapt this to your data.
secteurs (reader ESRISHAPE_1)
    attributes: secteur_ID long
    -> Tester
Tester
    BOOL_OP = OR
    COMPOSITE_TEST = 1
    TEST_CLAUSE = TEST @Value(secteur_ID) = 13
    TEST_MODE = TEST
    PASSED -> Clipper [CLIPPER]
mo6_couverture_du_sol_surf_tot (reader POSTGIS_1)
    attributes: idobj varchar(40),PrimaryKey, desnat varchar(30), typcou varchar(15), source varchar(15), base varchar(30), fksurf varchar(40)
    -> Clipper [CLIPPEE]
batiments_canton (reader POSTGIS_1)
    attributes: numcom int2, numele char(5), desnat char(30), mutmut char(8), desspe char(30), surfba int4, batddp int4, datedt date, typcou char(15), nufeco char(5), ideddp char(8), desba1 char(30), desba2 char(30), desba3 char(30), source char(30)
    -> Tester_2
Tester_2
    BOOL_OP = OR
    COMPOSITE_TEST = 1
    TEST_CLAUSE = TEST @Value(typcou) NOT_= souterrain
    TEST_MODE = TEST
    PASSED -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeValueMapper
AttributeValueMapper
    DEFAULT_VALUE = hard
    DIRECTION = Forward (Source To Destination)
    LUT = dure,hard,bois,forest,ordinaire,hard,sans végétation,hard,verte,green,eau,water
    SRC = typcou
    VAL_ATTR = covertype
    -> AttributeKeeper
AttributeKeeper
    KEEP_ATTRS = covertype
    -> Counter
Counter
    CNT_ATTR = id
    DOMAIN = counter
    SCOPE = Global
    START = 1
    -> landcover (writer ESRISHAPE_2)
landcover (writer ESRISHAPE_2)
    attributes: covertype char(200), id char(200)
