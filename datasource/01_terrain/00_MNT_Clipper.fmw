FME workspace 00_MNT_Clipper.fmw

Parameters:
- DestDataset_GEOTIFF = .   # Destination GeoTIFF Folder
- SourceDataset_ESRISHAPE = ..\..\datasource\00_perimeter\secteurs.shp   # Source Esri Shapefile(s)
- SourceDataset_GEOTIFF_3 = \\nesitn8\z$\geodata\Nelidar2016\5_Grid\mnt\25cm\mnt2016_25cm_final.tif   # Source GeoTIFF File(s)

Readers:
- ESRISHAPE_1: ESRISHAPE from $(SourceDataset_ESRISHAPE)
- GEOTIFF_1: GEOTIFF from $(SourceDataset_GEOTIFF_3)

Writers:
- GEOTIFF_2: GEOTIFF to $(DestDataset_GEOTIFF) in EPSG:2056

Note: Clips an MNT.
secteurs (reader ESRISHAPE_1)
    attributes: secteur_ID long
    -> Clipper [CLIPPER]
Note: Original dataset not provided
GEOTIFF (reader GEOTIFF_1)
    -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> GEOTIFF (writer GEOTIFF_2)
GEOTIFF (writer GEOTIFF_2)
