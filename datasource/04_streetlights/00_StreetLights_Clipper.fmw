FME workspace 00_StreetLights_Clipper.fmw

Parameters:
- SourceDataset_SHAPEFILE_3 = \\wssgrf009\c$\Projects\sitn-vr\datasource\00_perimeter\perimeter.shp   # Source Esri Shapefile(s)
- FEATURE_TYPES_2 =
- DestDataset_ESRISHAPE = .   # Destination Esri Shapefile Folder

Readers:
- SHAPEFILE_1: SHAPEFILE from $(SourceDataset_SHAPEFILE_3) in EPSG:2056

Writers:
- ESRISHAPE_1: ESRISHAPE to $(DestDataset_ESRISHAPE) in EPSG:2056

secteurs (reader SHAPEFILE_1)
    attributes: secteur_ID long
    -> FeatureReader [INITIATOR]
Note: CHANGE YOUR SOURCE HERE
FeatureReader
    ATTRIBUTES = cadastre_souterrain.csel5_eclairage_public,"idobj,determination_planimetrique,etat,producteur_donnees,remarque,type,type_code,hauteur,date_construction,date_creation,date_modification,modification,creation,numcom,photographie,label"
    ATTR_ACCUM_MODE = Only Use Result
    COMBINE_GEOM = Use Result
    DATASET = nesitn2
    FEATURETYPES = cadastre_souterrain.csel5_eclairage_public
    FORMAT = POSTGIS
    INTERACT = Initiator Contains Result
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = nesitn2
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    cadastre_souterrain.csel5_eclairage_public -> Tester
Tester
    BOOL_OP = OR
    COMPOSITE_TEST = 1
    TEST_CLAUSE = TEST @Value(type) = Candelabre
    TEST_MODE = TEST
    PASSED -> streetlights (writer ESRISHAPE_1)
streetlights (writer ESRISHAPE_1)
    attributes: idobj char(200)
