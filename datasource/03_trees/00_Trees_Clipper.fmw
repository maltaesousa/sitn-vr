FME workspace 00_Trees_Clipper.fmw

Parameters:
- DestDataset_ESRISHAPE = H:\diffusion\h18\trees   # Destination Esri Shapefile Folder
- SourceDataset_MAPINFO_3 = \\wssgrf008\e$\10_Trees\TreeTops\canton_v2\arbres2016_v2_final.tab   # Source MapInfo TAB File(s)
- SourceDataset_ESRISHAPE = C:\Projects\sitn-vr\datasource\00_perimeter\perimeter.shp   # Source Esri Shapefile(s)
- DestDataset_ESRISHAPE_3 = C:\Projects\sitn-vr\datasource\03_trees   # Destination Esri Shapefile Folder

Readers:
- MAPINFO_2: MAPINFO from $(SourceDataset_MAPINFO_3) in CH1903Plus_1.LV95/01
- ESRISHAPE_3: ESRISHAPE from $(SourceDataset_ESRISHAPE)

Writers:
- ESRISHAPE_1: ESRISHAPE to $(DestDataset_ESRISHAPE) in CH1903Plus_1.LV95/01
- ESRISHAPE_2: ESRISHAPE to $(DestDataset_ESRISHAPE_3)

perimeter (reader ESRISHAPE_3)
    attributes: secteur_ID long
    -> Clipper [CLIPPER]
arbres2016_v2_final (reader MAPINFO_2)
    attributes: _rowid char(40), easting float, northing float, elevation float, fam_arbre char(20), hauteur float, hauteur_int integer
    -> Clipper [CLIPPEE]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> Counter
Counter
    CNT_ATTR = id
    DOMAIN = counter
    SCOPE = Global
    START = 0
    -> AttributeRenamer
AttributeRenamer
    ATTR_TABLE = RENAME_SET_DEFAULT hauteur_int > haut_int
    -> arbres2016 (writer ESRISHAPE_2)
arbres2016 (writer ESRISHAPE_2)
    attributes: id long, easting double, northing double, elevation double, fam_arbre char(20), hauteur double, haut_int long
