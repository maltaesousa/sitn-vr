FME workspace 00_Buildings_Clipper.fmw

Parameters:
- SourceDataset_SHAPEFILE_3 = ..\00_perimeter\secteurs.shp   # Source Esri Shapefile(s)
- FEATURE_TYPES_2 =
- DestDataset_ESRISHAPE = .   # Destination Esri Shapefile Folder

Readers:
- SHAPEFILE_1: SHAPEFILE from $(SourceDataset_SHAPEFILE_3) in EPSG:2056

Writers:
- ESRISHAPE_1: ESRISHAPE to $(DestDataset_ESRISHAPE) in EPSG:2056

secteurs (reader SHAPEFILE_1)
    attributes: secteur_ID long
    -> FeatureReader [INITIATOR]
Note: CHANGE YOUR SOURCE HERE
FeatureReader
    ATTR_ACCUM_MODE = Only Use Result
    COMBINE_GEOM = Use Result
    COORDSYS = EPSG:2056
    DATASET = C:\Users\Maltas\Desktop\MAS_DATA\canton\*.shp
    FORMAT = SHAPEFILE
    INTERACT = Initiator Contains Result
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_REPORT_BAD_GEOMETRY = No
    SHAPEFILE_TRIM_PRECEDING_SPACES = Yes
    SHAPEFILE_USE_SEARCH_ENVELOPE = NO
    <SCHEMA> -> secteurs (writer ESRISHAPE_1)
    <OTHER> -> secteurs (writer ESRISHAPE_1)
secteurs (writer ESRISHAPE_1)
    attributes: secteur_ID long, fme_featur char(50)
