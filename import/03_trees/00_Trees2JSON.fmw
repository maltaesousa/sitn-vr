FME workspace 00_Trees2JSON.fmw

Parameters:
- SourceDataset_ESRISHAPE = C:\Projects\sitn-vr\datasource\03_trees\arbres2016.shp   # Source Esri Shapefile(s)
- SourceDataset_ESRISHAPE_3 = C:\Projects\sitn-vr\datasource\00_perimeter\perimeter.shp   # Source Esri Shapefile(s)
- DestDataset_TEXTLINE = C:\Projects\sitn-vr\unity\Assets\Models\trees.json   # Destination Text File
- prot0_height = 18   # Height of tree prototype 0
- prot1_height = 28   # Height of tree prototype 1

Readers:
- ESRISHAPE_1: ESRISHAPE from $(SourceDataset_ESRISHAPE)
- ESRISHAPE_2: ESRISHAPE from $(SourceDataset_ESRISHAPE_3)

Writers:
- TEXTLINE_1: TEXTLINE to $(DestDataset_TEXTLINE)

Note: Trees points
arbres2016 (reader ESRISHAPE_1)
    attributes: id long, easting number(31,15), northing number(31,15), elevation number(31,15), fam_arbre char(20), hauteur number(31,15), haut_int long
    -> FeatureMerger [REQUESTOR]
perimeter (reader ESRISHAPE_2)
    attributes: secteur_ID long
    -> BoundsExtractor
BoundsExtractor
    XMAX = _xmax
    XMIN = _xmin
    YMAX = _ymax
    YMIN = _ymin
    -> FeatureMerger [SUPPLIER]
Note: Adds bounds information to trees
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator_2
Note: AttributeCreator_2 [AttributeCreator] / Attributes To Create: New AttributeAttribute Valueunity_x@Evaluate((@Value(easting)-@Value(_xmin))/(@Value(_xmax)-@Value(_xmin)))unity_z@Evaluate((@Value(northing)-@Value(_ymin))/(@Value(_ymax)-@Value(_ymin)))prototypeIndex<2 Possible Values>heightscale<2 Possible Values>widthScale@Value(heightscale)feature { / "coordinates": [@Value(unity_x), @Value(unity_z)], / "prototypeIndex": @Value(prototypeIndex), / "heightScale": @Format(%.1f,@Value(heightscale)), / "widthScale": @Format(%.1f,@Value(widthScale)) / ...
AttributeCreator_2
    ATTR_TABLE:
      SET_TO unity_x = @Evaluate((@Value(easting)-@Value(_xmin))/(@Value(_xmax)-@Value(_xmin)))
      SET_TO unity_z = @Evaluate((@Value(northing)-@Value(_ymin))/(@Value(_ymax)-@Value(_ymin)))
      SET_TO prototypeIndex = FME_CONDITIONAL:DEFAULT_VALUE'1'BOOL_OP;OR;COMPOSITE_TEST;1;TEST @Value(fam_arbre) = feuillu'0'FME_NUM_CONDITIONS2___
      SET_TO heightscale = FME_CONDITIONAL:DEFAULT_VALUE'@Evaluate(@Evaluate(@min(@Value(hauteur)/$(prot1_height),2)))'BOOL_OP;OR;COMPOSITE_TEST;1;TEST @Value(prototypeIndex) = 0'@Evaluate(@min(@Value(hauteur)/$(prot0_height),2))'FME_NUM_CONDITIONS2___
      SET_TO widthScale = @Value(heightscale)
      SET_TO feature =   {
            "coordinates": [@Value(unity_x), @Value(unity_z)],
            "prototypeIndex": @Value(prototypeIndex),
            "heightScale": @Format(%.1f,@Value(heightscale)),
            "widthScale": @Format(%.1f,@Value(widthScale))
          }
    -> Aggregator
Note: Concatenates all features separating them by a comma
Aggregator
    ACCUM_ATTRS_NAME = Use Attributes From One Feature
    AGGREGATE_TYPE = Homogeneous Collection (If Possible)
    CONCAT_ATTRS = feature
    MODE = Geometry - Assemble One Level
    SEP = ",\n"
    AGGREGATE -> AttributeCreator
Note: AttributeCreator [AttributeCreator] / Attributes To Create: New AttributeAttribute Valuetext_line_data{ "trees": [ / @Value(feature) / ]}
AttributeCreator
    ATTR_TABLE:
      SET_TO text_line_data = { "trees": [
        @Value(feature)
        ]}
    -> text_line (writer TEXTLINE_1)
Note: Writes JSON
text_line (writer TEXTLINE_1)
    attributes: text_line_data buffer
