FME workspace 90_CityGMLtoOBJ.fmw

Parameters:
- SourceDataset_SHAPEFILE = ..\..\datasource\00_perimeter\secteurs.shp   # Source Esri Shapefile(s)
- DestDataset_OBJ = .   # Destination OBJ Folder

Readers:
- SHAPEFILE_1: SHAPEFILE from $(SourceDataset_SHAPEFILE)

Writers:
- OBJ_1: OBJ to $(DestDataset_OBJ)

Note: This was a test and has not been used
secteurs (reader SHAPEFILE_1)
    attributes: secteur_ID long
    -> BoundsExtractor
BoundsExtractor
    XMAX = _xmax
    XMIN = _xmin
    YMAX = _ymax
    YMIN = _ymin
    -> FeatureReader [INITIATOR]
FeatureReader
    ATTRIBUTES = citydb.surface_geometry,"id,gmlid,gmlid_codespace,parent_id,root_id,is_solid,is_composite,is_triangulated,is_xlink,is_reverse,cityobject_id"
    ATTR_ACCUM_MODE = Merge Initiator and Result
    ATTR_CONFLICT_RES = Use Result
    COMBINE_GEOM = Use Result
    COORDSYS = EPSG:2056
    DATASET = 3DCityDB.org
    FEATURETYPES = citydb.surface_geometry
    FORMAT = POSTGIS
    INTERACT = Initiator Intersects Result
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = 3DCityDB.org
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    citydb.surface_geometry -> Offsetter
Offsetter
    MODE = Cartesian Coordinate
    XOFF = 0-@Value(_xmin)
    YOFF = 0-@Value(_ymin)
    ZOFF = 0
    OFFSET -> 3DAffiner
3DAffiner
    A = -1
    B = 0
    C = 0
    D = 0
    E = 0
    F = 0
    G = 1
    H = 0
    I = 0
    J = 1
    K = 0
    L = 0
    AFFINED -> AttributeCreator
AttributeCreator
    ATTR_TABLE:
      SET_TO obj_group = @Value(cityobject_id)
      SET_TO obj_object = @Value(gmlid)
    -> GeometryPropertySetter
GeometryPropertySetter
    OVERWRITE_CHOICE = Yes
    REMOVE_ATTRIBUTE = No
    SETTYPE_PARAM = Traits From Attributes
    SRC_ATTRS = obj_group obj_object
    SET -> 00_buildings (writer OBJ_1)
    SET -> CoordinateSwapper_Output
00_buildings (writer OBJ_1) [off]
CoordinateSwapper_Output: Inspector
