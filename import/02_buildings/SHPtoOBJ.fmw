FME workspace SHPtoOBJ.fmw

Parameters:
- SourceDataset_SHAPEFILE = ""C:\Users\Maltas\Desktop\MAS_DATA\Unity\Projects\Proto01\datasource\02_buildings\s1a10_ground_polygon.shp" "C:\Users\Maltas\Desktop\MAS_DATA\Unity\Projects\Proto01\datasource\02_buildings\s1a10_overhang_polygon.shp" "C:\Users\Maltas\Desktop\MAS_DATA\Unity\Projects\Proto01\datasource\02_buildings\s1a10_roof_polygon.shp" "C:\Users\Maltas\Desktop\MAS_DATA\Unity\Projects\Proto01\datasource\02_buildings\s1a10_roofsuperstructure_polygon.shp" "C:\Users\Maltas\Desktop\MAS_DATA\Unity\Projects\Proto01\datasource\02_buildings\s1a10_shed_polygon.shp" "C:\Users\Maltas\Desktop\MAS_DATA\Unity\Projects\Proto01\datasource\02_buildings\s1a10_wall_polygon.shp" "C:\Users\Maltas\Desktop\MAS_DATA\Unity\Projects\Proto01\datasource\02_buildings\s1a10_wallsuperstructure_polygon.shp""   # Source Esri Shapefile(s)
- DestDataset_OBJ = C:\Users\Maltas\Desktop\MAS_DATA\Unity\Projects\Proto01\import\02_buildings   # Destination OBJ Folder
- SourceDataset_SHAPEFILE_3 = C:\Users\Maltas\Desktop\MAS_DATA\Unity\Projects\Proto01\datasource\00_perimeter\secteurs.shp   # Source Esri Shapefile(s)

Readers:
- SHAPEFILE_1: SHAPEFILE from $(SourceDataset_SHAPEFILE)
- SHAPEFILE_2: SHAPEFILE from $(SourceDataset_SHAPEFILE_3)

Writers:
- OBJ_1: OBJ to $(DestDataset_OBJ)

s1a10_roofsuperstructure_polygon (reader SHAPEFILE_1)
    attributes: BuildingId char(32), Area double, Azimuth double, secteur_ID long, fme_featur char(50)
    -> Aggregator
s1a10_wallsuperstructure_polygon (reader SHAPEFILE_1)
    attributes: BuildingId char(32), Area double, Azimuth double, secteur_ID long, fme_featur char(50)
    -> Aggregator
s1a10_ground_polygon (reader SHAPEFILE_1)
    attributes: BuildingId char(254), Area double, secteur_ID long, fme_featur char(50)
    -> Aggregator
s1a10_overhang_polygon (reader SHAPEFILE_1)
    attributes: BuildingId char(32), Area double, Azimuth double, Slope double, secteur_ID long, fme_featur char(50)
    -> Aggregator
secteurs (reader SHAPEFILE_2)
    attributes: secteur_ID long
    -> BoundsExtractor
BoundsExtractor
    XMAX = _xmax
    XMIN = _xmin
    YMAX = _ymax
    YMIN = _ymin
    -> AttributeKeeper
AttributeKeeper
    KEEP_ATTRS = _ymin,_xmin
    -> FeatureMerger [SUPPLIER]
s1a10_roof_polygon (reader SHAPEFILE_1)
    attributes: BuildingId char(32), Area double, Azimuth double, Slope double, secteur_ID long, fme_featur char(50)
    -> Aggregator
s1a10_shed_polygon (reader SHAPEFILE_1)
    attributes: CouvId char(32), COUVID char(200), BuildingId char(32), secteur_ID long, fme_featur char(50)
    -> Aggregator
s1a10_wall_polygon (reader SHAPEFILE_1)
    attributes: BuildingId char(32), Area double, Azimuth double, secteur_ID long, fme_featur char(50)
    -> Aggregator
Aggregator
    ACCUM_ATTRS_NAME = Use Attributes From One Feature
    AGGREGATE_TYPE = Homogeneous Collection (If Possible)
    GROUP_BY = BuildingId CouvId COUVID
    MODE = Geometry - Assemble One Level
    SEP = ,
    AGGREGATE -> FeatureMerger [REQUESTOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Offsetter
Offsetter
    MODE = Cartesian Coordinate
    XOFF = 0-@Value(_xmin)
    YOFF = 0-@Value(_ymin)
    ZOFF = 0
    OFFSET -> CoordinateSwapper
CoordinateSwapper
    SWAP_TYPE = Y <-> Z
    -> CoordinateSwapper_2
CoordinateSwapper_2
    SWAP_TYPE = X <-> Z
    -> Chopper [off]
    -> 00_buildings (writer OBJ_1) [off]
    -> FeatureMerger_Merged
00_buildings (writer OBJ_1)
Chopper [off]
    DEAGGREGATE_INPUT = Deaggregate
    MAX_VERTICES = 4
    MODE = By Vertex
    REMNANT_ATTR = _remnant
FeatureMerger_Merged: Inspector
