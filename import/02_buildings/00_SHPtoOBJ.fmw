FME workspace 00_SHPtoOBJ.fmw

Parameters:
- DestDataset_OBJ = .   # Destination OBJ Folder
- DestDataset_3DS = ..\..\unity\Assets\Models\Buildings   # Destination Autodesk 3ds Folder
- SourceDataset_ACAD = ..\..\datasource\02_buildings\102310.dwg   # Source Autodesk AutoCAD DWG/DXF File(s)
- SourceDataset_SHAPEFILE = C:\Projects\sitn-vr\datasource\00_perimeter\perimeter.shp   # Source Esri Shapefile(s)

Readers:
- ACAD_1: ACAD from $(SourceDataset_ACAD)
- SHAPEFILE_1: SHAPEFILE from $(SourceDataset_SHAPEFILE)

Writers:
- OBJ_1: OBJ to $(DestDataset_OBJ)
- 3DS_1: 3DS to $(DestDataset_3DS)

Note: Perimeter
perimeter (reader SHAPEFILE_1)
    attributes: secteur_ID long
    -> BoundsExtractor_2
BoundsExtractor_2
    XMAX = _xmax
    XMIN = _xmin
    YMAX = _ymax
    YMIN = _ymin
    -> AttributeKeeper_2
AttributeKeeper_2
    KEEP_ATTRS = _ymin,_xmin
    -> FeatureReader [INITIATOR]
    -> FeatureMerger [SUPPLIER]
Note: Load buildings depending on bounds of perimeter
FeatureReader
    ATTRIBUTES = Ground,"BuildingId,Area,secteur_ID,fme_featur",Overhang,"BuildingId,Area,Azimuth,Slope,secteur_ID,fme_featur",Roof,"BuildingId,Area,Azimuth,Slope,secteur_ID,fme_featur",RoofSuperstructure,"BuildingId,Area,Azimuth,secteur_ID,fme_featur",Wall,"BuildingId,Area,Azimuth,secteur_ID,fme_featur",WallSuperstructure,"BuildingId,Area,Azimuth,secteur_ID,fme_featur"
    ATTR_ACCUM_MODE = Prefix Initiator
    ATTR_PREFIX = sec_
    COMBINE_GEOM = Use Result
    DATASET = ""C:\Projects\sitn-vr\datasource\02_buildings\Ground.shp" "C:\Projects\sitn-vr\datasource\02_buildings\Overhang.shp" "C:\Projects\sitn-vr\datasource\02_buildings\Roof.shp" "C:\Projects\sitn-vr\datasource\02_buildings\RoofSuperstructure.shp" "C:\Projects\sitn-vr\datasource\02_buildings\Wall.shp" "C:\Projects\sitn-vr\datasource\02_buildings\WallSuperstructure.shp""
    FORMAT = SHAPEFILE
    INTERACT = Initiator Contains Result
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_REPORT_BAD_GEOMETRY = No
    SHAPEFILE_TRIM_PRECEDING_SPACES = Yes
    SHAPEFILE_USE_SEARCH_ENVELOPE = NO
    Ground -> Ground
    Overhang -> Overhang
    Roof -> Roof
    RoofSuperstructure -> RoofSuperstructure
    Wall -> Wall
    WallSuperstructure -> WallSuperstructure
Note: Manually corrected geometries
Problems (reader ACAD_1)
    -> AttributeExposer
AttributeExposer
    ATTR_LIST = fme_basename
    -> AttributeCreator_7
AttributeCreator_7
    ATTR_TABLE = SET_TO BuildingId = @Value(fme_basename)
    -> GeometryCoercer
GeometryCoercer
    GQUERY:
      for $geom in //geometry
      where $geom/count(parent::geometry) = 0
      return number($geom/@fme_id)
    KIND = fme_composite_surface
    COERCED -> FeatureMerger [REQUESTOR]
Note: Ground, Wall and Roof are mandatories. This allows to Load CityGML and connect elements here.
FeatureMerger
    ATTR_ACCUM_MODE = Prefix Supplier
    IGNORE_NULLS = No
    JOIN_KEYS = 1 1 AUTO
    MERGE_TYPE = Attributes Only
    PROCESS_DUPS = NO
    REJECT_NULL_MISSING_KEYS = No
    SUPPLIERS_FIRST = No
    SUPPLIER_PREFIX = sec_
    MERGED -> Wall
Note: Simplify composites
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> FaceReplacer
Note: Replace 3D polygones with Faces
FaceReplacer
    ANGULAR_TOLERANCE_CHOICE = Ignore
    THICKNESS_TOLERANCE_CHOICE = Ignore
    -> AttributeFilter
    <REJECTED> -> AttributeFilter
Note: Separate walls from roof in order to texture it
AttributeFilter
    ATTR_NAME = BuildingPart
    ATTR_VALUES = <Empty>,<Missing>,<Null>,<Unfiltered>,Ground,Wall,WallSuperstructure,Roof,RoofSuperstructure,Overhang
    <EMPTY> -> AppearanceSetter [GEOMETRY]
    <MISSING> -> AppearanceSetter [GEOMETRY]
    <NULL> -> AppearanceSetter [GEOMETRY]
    <UNFILTERED> -> AppearanceSetter [GEOMETRY]
    Ground -> AppearanceSetter [GEOMETRY]
    Wall -> AppearanceSetter [GEOMETRY]
    WallSuperstructure -> AppearanceSetter [GEOMETRY]
    Roof -> AppearanceSetter_2 [GEOMETRY]
    RoofSuperstructure -> AppearanceSetter_2 [GEOMETRY]
    Overhang -> AppearanceSetter_2 [GEOMETRY]
Note: Separate core building and roofs
AttributeFilter_2
    ATTR_NAME = BuildingPart
    ATTR_VALUES = <Empty>,<Missing>,<Null>,<Unfiltered>,Ground,Wall,WallSuperstructure,Roof,RoofSuperstructure,Overhang
    <EMPTY> -> SolidBuilder
    <MISSING> -> SolidBuilder
    <NULL> -> SolidBuilder
    <UNFILTERED> -> SolidBuilder
    Ground -> SolidBuilder
    Wall -> SolidBuilder
    WallSuperstructure -> SolidBuilder
    Roof -> SolidBuilder
    Roof -> SurfaceDissolver_2
    RoofSuperstructure -> SolidBuilder
    RoofSuperstructure -> SurfaceDissolver_2
    Overhang -> SurfaceDissolver_2
SolidBuilder
    ACCUM_ATTRS_NAME = Use Attributes From One Feature
    DROP_HOLES = No
    GROUP_BY = BuildingId
    HOLE_ATTR = _is_void
    SOLID -> SolidDissolver [Solids]
    UNUSED -> Extruder
Note: In case core building cannot be created, extrude walls so they become solids
Extruder
    DIRECTION = Auto
    DISTANCE = 0.001
    EXTRUDED -> SolidDissolver [Solids]
Note: Simplify coplanar surfaces
SurfaceDissolver_2
    ACCUM_INPUT_ATTRS = Use Attributes From One Feature
    DEAGGREGATE_INPUT = Yes
    GROUP_BY = BuildingId
    MATCHING_APPS = No
    NORMAL_TOLERANCE = 1
    OFFSET_TOLERANCE = 1
    SEPARATE_SURFACES = No
    SURFACE -> Extruder_3
    <REJECTED> -> Extruder_3
Extruder_3
    DIRECTION = Vertical
    DISTANCE = -0.2
    EXTRUDED -> Offsetter
Note: Avoid collision with core building
Offsetter
    MODE = Cartesian Coordinate
    XOFF = 0
    YOFF = 0
    ZOFF = .01
    OFFSET -> Aggregator
Note: Group roof parts
Aggregator
    ACCUM_ATTRS_NAME = Use Attributes From One Feature
    AGGREGATE_TYPE = Homogeneous Collection (If Possible)
    GROUP_BY = BuildingId
    MODE = Geometry - Assemble One Level
    SEP = ,
    AGGREGATE -> Scaler
Note: Avoid vertical collisions with core building
Scaler
    RASTER_SCALING = Extents
    SCALE_ORIGIN = Center Point
    TEXT_LOC_ONLY = Location and Size
    XSCALE = 1.001
    YSCALE = 1.001
    ZSCALE = 1.001
    SCALED -> SolidDissolver [Solids]
Note: Boolean union of solids
SolidDissolver
    Av_1:
      from re import sub
      if (FME_MacroValues['Av']==''):
          return "pyfme_none"
      else:
          Av=sub(","," ",FME_MacroValues['Av'],)
          return Av
    Concat_1:
      from re import sub
      if (FME_MacroValues['Concat']==''):
          return "pyfme_none"
      else:
          Concat=sub(","," ",FME_MacroValues['Concat'],)
          return Concat
    Group = BuildingId
    Group_1:
      from re import sub
      if (FME_MacroValues['Group']==''):
          return "pyfme_none"
      else:
          group=sub(","," ",FME_MacroValues['Group'],)
          return group
    List_1:
      if FME_MacroValues['List'] == "":
          return "pyfme_list"
      else:
          return FME_MacroValues['List']
    Sum_1:
      from re import sub
      if (FME_MacroValues['Sum']==''):
          return "pyfme_none"
      else:
          Sum=sub(","," ",FME_MacroValues['Sum'],)
          return Sum
    Dissolved -> Offsetter_3
Note: Set to Unity coordinates
Offsetter_3
    MODE = Cartesian Coordinate
    XOFF = 0-@Value(sec__xmin)
    YOFF = 0-@Value(sec__ymin)
    ZOFF = 0
    OFFSET -> 3DAffiner_2 [off]
    OFFSET -> 3DAffiner_3
3DAffiner_2 [off]
    A = -1
    B = 0
    C = 0
    D = 0
    E = 0
    F = 0
    G = 1
    H = 0
    I = 0
    J = 1
    K = 0
    L = 0
    AFFINED -> 00_buildingsOBJ (writer OBJ_1) [off]
00_buildingsOBJ (writer OBJ_1) [off]
3DAffiner_3
    A = -1
    B = 0
    C = 0
    D = 0
    E = 0
    F = -1
    G = 0
    H = 0
    I = 0
    J = 0
    K = 1
    L = 0
    AFFINED -> 00_3DS (writer 3DS_1)
Note: Writer 3DS
00_3DS (writer 3DS_1)

Bookmark: MODEL ABSTRACTION
Ground: AttributeCreator
    ATTR_TABLE = SET_TO BuildingPart = Ground
    -> Deaggregator
Overhang: AttributeCreator
    ATTR_TABLE = SET_TO BuildingPart = Overhang
    -> Deaggregator
Roof: AttributeCreator
    ATTR_TABLE = SET_TO BuildingPart = Roof
    -> Deaggregator
RoofSuperstructure: AttributeCreator
    ATTR_TABLE = SET_TO BuildingPart = RoofSuperstructure
    -> Deaggregator
WallSuperstructure: AttributeCreator
    ATTR_TABLE = SET_TO BuildingPart = WallSuperstructure
    -> Deaggregator
Wall: AttributeCreator
    ATTR_TABLE = SET_TO BuildingPart = Wall
    -> Deaggregator

Bookmark: SET COLORS
AppearanceSetter
    APPEARANCE_NAME = white
    DEF_STORAGE = Create New Definitions
    DIFFUSE_COLOR = 1,1,1
    GQUERY:
      for $geom in //geometry
      where $geom/count(parent::geometry) = 0
      return number($geom/@fme_id)
    SET_ON_SIDE = Front Side
    SHININESS = 0
    TEXTURE_MAPPING_TYPE_CHOICE = Surface Normal
    TEXTURE_U_OFFSET2 = 0.0
    TEXTURE_U_SCALE_FACTOR = 1
    TEXTURE_V_OFFSET2 = 0.0
    TEXTURE_V_SCALE_FACTOR = 1
    USE_EXISTING_TEXTURE_COORDINATES = No
    -> AttributeFilter_2
AppearanceSetter_2
    APPEARANCE_NAME = roof
    DEF_STORAGE = Create New Definitions
    DIFFUSE_COLOR = 0.317647,0.12549,0.0352941
    GQUERY:
      for $geom in //geometry
      where $geom/count(parent::geometry) = 0
      return number($geom/@fme_id)
    SET_ON_SIDE = Front and Back Sides
    SHININESS = 0
    TEXTURE_MAPPING_TYPE_CHOICE = From Top View
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> AttributeFilter_2

FME custom transformer SolidDissolver
The SolidDissolver dissolves adjoining solids into a single feature. Any non-solid geometries will be output untouched through the <Rejected> port.
The SolidDissolver has the following parameters:
    Group By
If you do not select Group By attributes, then all features fall into the same group.
When you select Group By attributes, this transformer will dissolve the geometries of the input solid features, based on the selection in the Group By parameter. Each group of features that have the same values for the Group By attributes will be processed independently of other groups.
    Count Attribute
If a Count Attribute is entered, then an attribute with this name will be added to each output solid, containing the number of features that resulted in the output solid.
    Keep Input Attributes
If Keep Input Attributes is set to Yes, the attributes from the original features will be merged onto the output Dissolved features.
    List Name
If a List Name is specified, then all attributes of an input feature will be stored as part of a list attribute entry in the output Dissolved feature.
    Attributes to Concatenate
Attributes can be concatenated so that the resulting Dissolved feature preserves multiple source attribute values under the same attribute name. For example, if input feature 1 has an id attribute of 1 and input feature 2 has an id attribute of 2, specifying id for this parameter together with a separate character of , will cause the output Dissolved feature to have an id with value 1, 2.
    Separator Character
The Separator Character is used to separate elements within an attribute value string. For example, if features with attribute values of 'River Rd', 'Marine Dr' and 'HWY 1' for the attribute named 'Road Name' respectively, and the Separator Character is , (a comma followed by a space) on the output solid feature, the attribute 'Road Name' will contain 'River Rd, Marine Dr, HWY 1' as a value.
The separator character can be expressed as a regular character but it can also contain special characters beginning with a backslash ("\"), as specified in the following table.
If the sequence is not listed in the table, the backslash character is ignored. (For example, entering lan\es will be interpreted as lanes.) If no separator character is supplied, attributes will be concatenated without a separator.
    Sequence
    Description
\a Audible alert (bell) (0x07)
\b Backspace (0x08)
\f Form feed (0x0c)
\n Newline (0x0a)
\r Carriage return (0x0d)
\t Tab (0x09)
\v Vertical tab (0x0b)
\\ Backslash
(Note: A single backslash entered at the end of a value will be converted to an escaped backslash.)
    Attributes to Sum
Any attributes specified in this field will undergo statistical accumulation.
For example, if two input solids have an attribute 'salary' set to 30000 and 50000, then summing them would result in a 'salary' of 80000 on the dissolved output.
    Attributes to Average
Any attributes specified in this field will undergo statistical accumulation.
For example, if two input solids have an attribute 'salary' set to 30000 and 50000, then averaging them would result in a 'salary' of 40000 on the dissolved output.

Parameters:
- Group =   # " " Group By
- List =   # List Name
- Concat =   # " " Attributes to Concatenate
- Sum =   # " " Attributes to Sum
- Av =   # " " Attributes to Average
- Group_1:   # Python Script
      from re import sub
      if (FME_MacroValues['Group']==''):
          return "pyfme_none"
      else:
          group=sub(","," ",FME_MacroValues['Group'],)
          return group

Note: Refine geometry / to get all solids
GeometryRefiner
    -> GeometryFilter
Note: Force to brep solids
GeometryCoercer
    GQUERY:
      for $geom in //geometry
      where $geom/count(parent::geometry) = 0
      return number($geom/@fme_id)
    KIND = fme_brep_solid
    COERCED -> Aggregator
    UNTOUCHED -> Aggregator
Aggregator
    ACCUM_ATTRS_NAME = Yes
    AGGREGATE_TYPE = Homogeneous Collection (If Possible)
    GROUP_BY = $(Group_1)
    MODE = Geometry - Assemble One Level
    ORDERED = No
    AGGREGATE -> Dissolved (output)
Dissolved (output)

Bookmark: Input Data
Solids (input)
    -> GeometryRefiner

Bookmark: Filter out solids
GeometryFilter
    BREAK_AGG = No
    GEOM_PORT_NAMES = Point Line Arc Area Ellipse Text Raster "Point Cloud" Surface Solid Collection Null Instance
    POINT -> <Rejected> (output)
    LINE -> <Rejected> (output)
    ARC -> <Rejected> (output)
    AREA -> <Rejected> (output)
    ELLIPSE -> <Rejected> (output)
    TEXT -> <Rejected> (output)
    RASTER -> <Rejected> (output)
    POINTCLOUD -> <Rejected> (output)
    SURFACE -> <Rejected> (output)
    SOLID -> GeometryCoercer
    COLLECTION -> <Rejected> (output)
    NULL -> <Rejected> (output)
    INSTANCE -> <Rejected> (output)

Bookmark: Rejected features ignored
<Rejected> (output)
