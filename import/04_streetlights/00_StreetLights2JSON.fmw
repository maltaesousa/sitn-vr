FME workspace 00_StreetLights2JSON.fmw

Parameters:
- SourceDataset_ESRISHAPE_3 = C:\Projects\sitn-vr\datasource\00_perimeter\perimeter.shp   # Source Esri Shapefile(s)
- DestDataset_TEXTLINE = C:\Projects\sitn-vr\unity\Assets\Models\streetlights.json   # Destination Text File
- prot0_height = 18   # Height of tree prototype 0
- prot1_height = 28   # Height of tree prototype 1
- SourceDataset_SHAPEFILE = ..\..\datasource\04_streetlights\streetlights.shp   # Source Esri Shapefile(s)
- SourceDataset_SHAPEFILE_3 = C:\Projects\sitn-vr\datasource\01_terrain\landcover.shp   # Source Esri Shapefile(s)

Readers:
- ESRISHAPE_1: ESRISHAPE from $(SourceDataset_ESRISHAPE_3)
- SHAPEFILE_1: SHAPEFILE from $(SourceDataset_SHAPEFILE)
- SHAPEFILE_2: SHAPEFILE from $(SourceDataset_SHAPEFILE_3)

Writers:
- TEXTLINE_1: TEXTLINE to $(DestDataset_TEXTLINE)

landcover (reader SHAPEFILE_2)
    attributes: covertype char(200), id char(200)
    -> Tester
Note: Only roads
Tester
    BOOL_OP = OR
    COMPOSITE_TEST = 1
    TEST_CLAUSE = TEST @Value(covertype) = hard
    TEST_MODE = TEST
    PASSED -> CenterLineReplacer
Note: Replace area by its center line
CenterLineReplacer
    MODE = Approximate Center Line
    CENTERLINE -> NeighborFinder [CANDIDATE]
streetlights (reader SHAPEFILE_1)
    attributes: idobj char(200)
    -> CoordinateExtractor
Note: Get coordinates from point geometry
CoordinateExtractor
    IND = 0
    MODE = Specify Coordinate
    X_ATTR = easting
    Y_ATTR = northing
    -> FeatureMerger [REQUESTOR]
perimeter (reader ESRISHAPE_1)
    attributes: secteur_ID long
    -> BoundsExtractor
Note: Extract: _xmin, _xmax, _ymin, _ymax
BoundsExtractor
    XMAX = _xmax
    XMIN = _xmin
    YMAX = _ymax
    YMIN = _ymin
    -> FeatureMerger [SUPPLIER]
Note: Merge bounds to streetlights
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> NeighborFinder [BASE]
Note: Every streetlight finds its closest road and gets azimut to it.
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> AttributeCreator_2
    UNMATCHED_BASE -> AttributeCreator_2
Note: AttributeCreator_2 [AttributeCreator] / Attributes To Create: New AttributeAttribute Valueunity_x@Evaluate((@Value(easting)-@Value(_xmin))/(@Value(_xmax)-@Value(_xmin)))unity_z@Evaluate((@Value(northing)-@Value(_ymin))/(@Value(_ymax)-@Value(_ymin)))prototypeIndex2heightscale1widthScale@Value(heightscale)rotation<2 Possible Values>feature { / "coordinates": [@Format(%.7f,@Value(unity_x)), @Format(%.7f,@Value(unity_z))], / "prototypeIndex": @Value(prototypeIndex), / "heightScale": @Format(%.2f,@Value(heightscale)), / "widthScale": @Format(%.2f,@Value(widthScale)), / ...
AttributeCreator_2
    ATTR_TABLE:
      SET_TO unity_x = @Evaluate((@Value(easting)-@Value(_xmin))/(@Value(_xmax)-@Value(_xmin)))
      SET_TO unity_z = @Evaluate((@Value(northing)-@Value(_ymin))/(@Value(_ymax)-@Value(_ymin)))
      SET_TO prototypeIndex = 2
      SET_TO heightscale = 1
      SET_TO widthScale = @Value(heightscale)
      SET_TO rotation = FME_CONDITIONAL:DEFAULT_VALUE'@Evaluate(@degToRad(90+(360-@Value(_angle))))'BOOL_OP;OR;COMPOSITE_TEST;1;TEST @Value(_angle) <= 90'@Evaluate(@degToRad(90-@Value(_angle)))'FME_NUM_CONDITIONS2___
      SET_TO feature =   {
            "coordinates": [@Format(%.7f,@Value(unity_x)), @Format(%.7f,@Value(unity_z))],
            "prototypeIndex": @Value(prototypeIndex),
            "heightScale": @Format(%.2f,@Value(heightscale)),
            "widthScale": @Format(%.2f,@Value(widthScale)),
            "rotation" : @Format(%.2f,@Value(rotation))
          }
    -> Aggregator
Note: Aggregator
Aggregator
    ACCUM_ATTRS_NAME = Use Attributes From One Feature
    AGGREGATE_TYPE = Homogeneous Collection (If Possible)
    CONCAT_ATTRS = feature
    MODE = Geometry - Assemble One Level
    SEP = ",\n"
    AGGREGATE -> AttributeCreator
Note: AttributeCreator [AttributeCreator] / Attributes To Create: New AttributeAttribute Valuetext_line_data{ "trees": [ / @Value(feature) / ]}
AttributeCreator
    ATTR_TABLE:
      SET_TO text_line_data = { "trees": [
        @Value(feature)
        ]}
    -> text_line (writer TEXTLINE_1)
Note: Writes JSON
text_line (writer TEXTLINE_1)
    attributes: text_line_data buffer
