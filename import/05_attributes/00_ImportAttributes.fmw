FME workspace 00_ImportAttributes.fmw

Parameters:
- SourceDataset_SHAPEFILE = C:\Projects\sitn-vr\datasource\02_buildings\Ground.shp   # Source Esri Shapefile(s)
- DestDataset_TEXTLINE = C:\Projects\sitn-vr\unity\Assets\Models   # Destination Text File
- DestDataset_TEXTLINE_5 = C:\Projects\sitn-vr\unity\Assets\Models   # Destination Text File
- DestDataset_TEXTLINE_4 = C:\Projects\sitn-vr\unity\Assets\Models   # Destination Text File
- SourceDataset_XLSXR = C:\Projects\sitn-vr\datasource\05_attributes\land_registry.xlsx   # Source Microsoft Excel File(s)

Readers:
- SHAPEFILE_1: SHAPEFILE from $(SourceDataset_SHAPEFILE)
- XLSXR_1: XLSXR from $(SourceDataset_XLSXR)

Writers:
- TEXTLINE_1: TEXTLINE to $(DestDataset_TEXTLINE)
- TEXTLINE_2: TEXTLINE to $(DestDataset_TEXTLINE_5)
- TEXTLINE_3: TEXTLINE to $(DestDataset_TEXTLINE_4)

Ground (reader SHAPEFILE_1)
    attributes: BuildingId char(254), Area double, secteur_ID long, fme_featur char(50)
    -> Tester
Tester
    BOOL_OP = OR
    COMPOSITE_TEST = 1
    TEST_CLAUSE = TEST @Value(BuildingId) IN 102328,102327,102325,102326,102322,102312,102351,102307,102305,102302,107870,107873,102301,102324,102295
    TEST_MODE = TEST
    PASSED -> CoordinateExtractor
CoordinateExtractor
    IND = 0
    MODE = Specify Coordinate
    Z_ATTR = _z
    -> FeatureMerger [REQUESTOR]
Feuil1 (reader XLSXR_1)
    attributes: id number(7,0), owner char(39), easements char(136)
    -> FeatureMerger [SUPPLIER]
FeatureMerger
    ATTR_ACCUM_MODE = Merge Supplier
    ATTR_CONFLICT_RES = Use Requestor
    IGNORE_NULLS = No
    JOIN_KEYS = @Value(BuildingId) @Value(id) AUTO
    MERGE_TYPE = Attributes Only
    PROCESS_DUPS = NO
    REJECT_NULL_MISSING_KEYS = No
    SUPPLIERS_FIRST = No
    MERGED -> AttributeCreator_3
AttributeCreator_3
    ATTR_TABLE:
      SET_TO feature =            { "@Value(BuildingId)", new Dictionary<string, string>
                        {
                            { "Aire", "@round(@Value(Area),0) m²"},
                            { "Altitude", "@Format(%.2f,@Value(_z)) m" },
                            { "Propriétaire", "@Value(owner)"},
                            { "Servitudes", "@Value(easements)"}
                        }
                    }
      SET_TO object_name = Building
    -> Aggregator
Aggregator
    ACCUM_ATTRS_NAME = Use Attributes From One Feature
    AGGREGATE_TYPE = Homogeneous Collection (If Possible)
    CONCAT_ATTRS = feature
    MODE = Geometry - Assemble One Level
    SEP = ",\n"
    AGGREGATE -> AttributeCreator
    AGGREGATE -> AttributeCreator_4
AttributeCreator_4
    ATTR_TABLE:
      SET_TO text_line_data = //======================================= 2019, Stéphane Malta e Sousa, sitn-vr =======================================
        //
        // This script was generated by FME: $(WORKSPACE_NAME)
        //
        //=====================================================================================================================

        using UnityEditor;
        using UnityEngine;
        using System.Collections.Generic;
        using System;
        using System.Text.RegularExpressions;

        namespace SITN
        {
            public class Queryable@Value(object_name): MonoBehaviour
            {
                public string aire;
                public string altitude;
                public string owner;
                public string easements;

                public Dictionary<string, string> GetData()
                {
                    return new Dictionary<string, string>() {
                        { "Aire: ", aire},
                        { "Altitude: ", altitude },
                        { "Propriétaire: ", owner },
                        { "Servitudes: ", easements },
                    };
                }

                public override string ToString()
                {
                    List<string> dataString = new List<string>();
                    dataString.Add("<line-height=150%>Aire: " + aire + ", altitude: " + altitude);
                    dataString.Add("<b><uppercase>Propriété de:</uppercase></b></line-height>");
                    dataString.Add(Regex.Replace(owner, @" et ", "<br>") + "<line-height=150%>");
                    dataString.Add("<b><uppercase>Servitudes:</uppercase></b></line-height>");
                    dataString.Add("<align=justified>" + easements);
                    return String.Join(Environment.NewLine, dataString.ToArray());
                }
            }
        }
    -> StringReplacer_4
StringReplacer_4
    CASE = NO
    FIND_TEXT = [\n|\r\n]
    NO_MATCH = _FME_NO_OP_
    REGEXP = YES
    REPLACE_TEXT = "\n"
    SRC_ATTRS = text_line_data
    -> text_line (writer TEXTLINE_3)
Note: QueryableBuilding
text_line (writer TEXTLINE_3)
    attributes: text_line_data buffer
AttributeCreator
    ATTR_TABLE:
      SET_TO text_line_data = //======================================= 2019, Stéphane Malta e Sousa, sitn-vr =======================================
        //
        // This script was generated by FME: $(WORKSPACE_NAME)
        //
        //=====================================================================================================================

        using UnityEditor;
        using UnityEngine;
        using System.Collections.Generic;
        using System;

        namespace SITN
        {
            public class @Value(object_name)DataImporter : ScriptableWizard
            {
                private List<string> notFounds = new List<string>();
                private Dictionary<string, Dictionary<string, string>> @LowerCase(@Value(object_name))s = new Dictionary<string, Dictionary<string, string>>
                {
        @Value(feature)
                };


                [MenuItem("SITN/Import @LowerCase(@Value(object_name)) data")]
                static void CreateWizard()
                {
                    ScriptableWizard.DisplayWizard<@Value(object_name)DataImporter>("Import @LowerCase(@Value(object_name)) data", "OK!");

                }


                void OnWizardCreate() { }
                void OnWizardUpdate()
                {
                    if (notFounds.ToArray().Length > 0)
                    {
                        helpString = String.Join(", ", notFounds.ToArray()) + " not found!";
                        helpString += Environment.NewLine;
                        helpString += "Please be sure the names used in this script match the names of your GameObjects.";
                    }
                }

                // Find objects and add attributes to them
                private void Awake()
                {
                    try
                    {
                        foreach (KeyValuePair<string, Dictionary<string, string>> entry in @LowerCase(@Value(object_name))s)
                        {
                            GameObject go = GameObject.Find(entry.Key);
                            if (go != null)
                            {
                                Process("Import", entry, go);
                            } else
                            {
                                notFounds.Add(entry.Key);
                            }
                        }
                    }
                    catch (UnityException)
                    {
                        EditorUtility.DisplayDialog("Error", "Something went terribly wrong!", "Cancel");
                        return;
                    }
                }

                private void Process(string mode, KeyValuePair<string, Dictionary<string, string>> entry, GameObject go)
                {
                    if (mode.ToLower() == "import")
                    {
                        QueryableBuilding qo = go.AddComponent<QueryableBuilding>();
                        qo.aire = entry.Value["Aire"];
                        qo.altitude = entry.Value["Altitude"];
                        qo.owner = entry.Value["Propriétaire"];
                        qo.easements = entry.Value["Servitudes"];
                        go.AddComponent<BoxCollider>();
                    }
                    else
                    {
                        DestroyImmediate(go.GetComponent<Queryable@Value(object_name)>());
                        DestroyImmediate(go.GetComponent<BoxCollider>());
                    }
                }
            }
        }
    -> StringReplacer
StringReplacer
    CASE = NO
    FIND_TEXT = [\n|\r\n]
    NO_MATCH = _FME_NO_OP_
    REGEXP = YES
    REPLACE_TEXT = "\n"
    SRC_ATTRS = text_line_data
    -> text_line (writer TEXTLINE_1)
    -> StringReplacer_2
Note: Importer
text_line (writer TEXTLINE_1)
    attributes: text_line_data buffer
StringReplacer_2
    CASE = YES
    FIND_TEXT = Import
    NO_MATCH = _FME_NO_OP_
    REGEXP = NO
    REPLACE_TEXT = Destroy
    SRC_ATTRS = text_line_data
    -> text_line (writer TEXTLINE_2)
Note: Destroyer
text_line (writer TEXTLINE_2)
    attributes: text_line_data buffer
